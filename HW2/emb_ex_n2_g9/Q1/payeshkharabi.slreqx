# payeshkharabi

## #1: A recieve timed events from B (Functional)

## #2: B output ok and missed (Functional)

## #3: A classify based on ok and missed (Functional)

## #4: It shouldbe secure (Container)

## #5: It should be testable and debuggable and tracable (Container)
