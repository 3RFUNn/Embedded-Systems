# reqs

## #1: Master sart the system (Functional)

## #2: Master provides physical address (Functional)

## #3: Provide internal register (Functional)

## #4: Data sent by master on write (Functional)

## #5: Data provide on slave on read (Functional)

## #6: Control the bus conflict through the protocol (Functional)

## #7: System being fast (Informational)

## #8: Scalability of slaves count (Functional)

## #9: No readtime time overhead (Functional)
